module validate-bgp-neighbor-state {

  namespace "http://example.com/validate-bgp-neighbor-state";
  prefix validate-bgp-neighbor-state;

  import ietf-inet-types {
    prefix inet;
  }
  import tailf-common {
    prefix tailf;
  }
  import tailf-ncs {
    prefix ncs;
  }

  description
    "Bla bla...";

  revision 2016-01-01 {
    description
      "Initial revision.";
  }

  container action {
    tailf:action double {
      tailf:actionpoint validate-bgp-neighbor-state-action;
      input {
        leaf device {
          type leafref {
            path "/ncs:devices/ncs:device/ncs:name";
          }
        }

        // bgp neighbor ipv4 address
        leaf bgp_neighbor_addr {
          type inet:ipv4-address;
        }
      }
      output {
        leaf bgp_state {
          type string;
        }
      }
    }
  }
}
